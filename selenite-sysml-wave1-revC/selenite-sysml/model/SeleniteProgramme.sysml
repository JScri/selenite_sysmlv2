package SeleniteProgramme {
    doc /* Selenite Programme — SysML v2 model root.
         *
         * A 200-year lunar rare earth element mining and processing
         * initiative targeting full replacement of terrestrial REE
         * mining at 2.5 Mt/yr REO by ~Y180.
         *
         * Baseline: ECN-019 Rev C + ECN-020.
         * ECN-021 (PKT process water) drafted, NOT propagated — excluded. Document-of-record traceability:
         * every definition carries a doc comment citing its source
         * document and revision. mapping/document_map.csv is the
         * master migration index.
         *
         * Package map:
         *   SelenitePhases          - phase enumeration P0-P14+, PhaseGated
         *                             base, year windows, F7 gap
         *   SeleniteSites           - seven programme nodes (SPA, PSR floor,
         *                             PKT, EML-2, PKT relay, DRO, Earth)
         *   SeleniteFleet           - robot fleet (fleet v9.md authority)
         *   SelenitePsrNetwork      - Shackleton PSR access/charging network
         *   SeleniteHabitat         - SPA/PKT crewed and fixed facilities
         *   SelenitePower           - SPA/PKT power, MSR fleet, F5
         *   SeleniteProcessing      - REE value chain, flowsheet, Th/U stage
         *   SeleniteTransport       - MD-1..5 (ECN-020), conveyors, links
         *   SeleniteInterfaces      - items, port defs, interface defs
         *                             (every connection typed, Wave 4B)
         *   SeleniteBehaviour       - the value chain as phase-gated action
         *                             flows (Wave 4B)
         *   SeleniteSoftware        - SENTINEL states and modes, ECN-014
         *                             auto-close machines, NAV-001 fusion
         *   SeleniteParameters      - exogenous inputs and gate thresholds
         *   SeleniteScenarios       - decisions D1-D8 (variations), uncertainty
         *                             register, trade studies, named scenarios
         *   SeleniteGates           - 81 decision gates, milestones M0-M8
         *   SeleniteRequirements    - committed architectural principles
         *   SeleniteAnalysis        - calcs (MATLAB remains authority)
         *   SeleniteConfigurations  - programme instance tree
         *
         * Wave 2 (14 September 2026): architecture and temporal skeleton;
         * Wave 3 (15 September 2026): gates, thresholds, phase bindings,
         * requirements, plan_check register - see CHANGELOG_WAVE3.md;
         * Wave 4A (6 November 2026): scenarios, uncertainty and decision
         * analysis, SEL-ECN-023 signed - see CHANGELOG_WAVE4A.md;
         * Wave 4B (7 November 2026): behaviour, interfaces and software -
         * see CHANGELOG_WAVE4B.md.
         */

    private import SeleniteConfigurations::*;
}
